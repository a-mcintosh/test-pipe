Gui.getDocument('Unnamed').resetEdit()
App.getDocument("Unnamed").removeObject("sk_star")
this_sketch = App.activeDocument().addObject('Sketcher::SketchObject','sk_star')

# -*- coding: utf-8 -*-

# Macro Begin: /home/amcintosh/Documents/FreeCAD/tests/Macro/star.FCMacro +++++++++++++++++++++++++++++++++++++++++++++++++
import FreeCAD

rot = App.Rotation(App.Vector(0, 0, 1),360/5)
ratio_inside = math.cos(2*math.pi/5)/math.cos(2*math.pi/10)
ratio_outside = math.cos(2*math.pi/10)
scale_factor = 1.0/(ratio_outside*ratio_inside)

FreeCAD.Console.PrintMessage("ratio inside " + str(ratio_inside) + "\n")
FreeCAD.Console.PrintMessage("ratio outside " + str(ratio_outside) + "\n")
FreeCAD.Console.PrintMessage("Scale factor " + str(scale_factor) + "\n")
vec = App.Vector(0, 25.4, 0)

vec2 = App.Vector(0, -1, 0)
vec2.Length = ratio_inside * vec.Length
vec2 = rot.multVec(vec2)
vec2 = rot.multVec(vec2)
vec2 = rot.multVec(vec2)
vec1 = vec2

App.ActiveDocument.sk_star.addGeometry(Part.LineSegment(vec,vec2),False)

vec = rot.multVec(vec)
App.ActiveDocument.sk_star.addGeometry(Part.LineSegment(vec,vec2),False)
vec2 = rot.multVec(vec2)
App.ActiveDocument.sk_star.addGeometry(Part.LineSegment(vec,vec2),False)
App.ActiveDocument.sk_star.addGeometry(Part.LineSegment(scale_factor*vec1,scale_factor*vec2),True)
vec1 = vec2

vec = rot.multVec(vec)
App.ActiveDocument.sk_star.addGeometry(Part.LineSegment(vec,vec2),False)
vec2 = rot.multVec(vec2)
App.ActiveDocument.sk_star.addGeometry(Part.LineSegment(vec,vec2),False)
App.ActiveDocument.sk_star.addGeometry(Part.LineSegment(scale_factor*vec1,scale_factor*vec2),True)
vec1 = vec2

vec = rot.multVec(vec)
App.ActiveDocument.sk_star.addGeometry(Part.LineSegment(vec,vec2),False)
vec2 = rot.multVec(vec2)
App.ActiveDocument.sk_star.addGeometry(Part.LineSegment(vec,vec2),False)
App.ActiveDocument.sk_star.addGeometry(Part.LineSegment(scale_factor*vec1,scale_factor*vec2),True)
vec1 = vec2

vec = rot.multVec(vec)
App.ActiveDocument.sk_star.addGeometry(Part.LineSegment(vec,vec2),False)
vec2 = rot.multVec(vec2)
App.ActiveDocument.sk_star.addGeometry(Part.LineSegment(vec,vec2),False)
App.ActiveDocument.sk_star.addGeometry(Part.LineSegment(scale_factor*vec1,scale_factor*vec2),True)
vec1 = vec2

vec = rot.multVec(vec)
App.ActiveDocument.sk_star.addGeometry(Part.LineSegment(vec,vec2),False)
vec2 = rot.multVec(vec2)
App.ActiveDocument.sk_star.addGeometry(Part.LineSegment(scale_factor*vec1,scale_factor*vec2),True)

#outer star
App.ActiveDocument.sk_star.addConstraint(Sketcher.Constraint('Coincident',2,1,1,1)) 
App.ActiveDocument.sk_star.addConstraint(Sketcher.Constraint('Coincident',0,2,1,2)) 
App.ActiveDocument.sk_star.addConstraint(Sketcher.Constraint('Coincident',5,1,4,1)) 
App.ActiveDocument.sk_star.addConstraint(Sketcher.Constraint('Coincident',8,1,7,1)) 
App.ActiveDocument.sk_star.addConstraint(Sketcher.Constraint('Coincident',11,1,10,1)) 
App.ActiveDocument.sk_star.addConstraint(Sketcher.Constraint('Coincident',13,1,0,1)) 
#inner star
App.ActiveDocument.sk_star.addConstraint(Sketcher.Constraint('Coincident',4,2,2,2)) 
App.ActiveDocument.sk_star.addConstraint(Sketcher.Constraint('Coincident',7,2,5,2)) 
App.ActiveDocument.sk_star.addConstraint(Sketcher.Constraint('Coincident',10,2,8,2)) 
App.ActiveDocument.sk_star.addConstraint(Sketcher.Constraint('Coincident',13,2,11,2))
# inner pentangle
App.ActiveDocument.sk_star.addConstraint(Sketcher.Constraint('Coincident',3,2,6,1)) 
App.ActiveDocument.sk_star.addConstraint(Sketcher.Constraint('Coincident',6,2,9,1)) 
App.ActiveDocument.sk_star.addConstraint(Sketcher.Constraint('Coincident',9,2,12,1)) 
App.ActiveDocument.sk_star.addConstraint(Sketcher.Constraint('Coincident',12,2,14,1)) 
App.ActiveDocument.sk_star.addConstraint(Sketcher.Constraint('Coincident',14,2,3,1)) 
#make arms have parallel segments
App.ActiveDocument.sk_star.addConstraint(Sketcher.Constraint('Parallel',0,4)) 
App.ActiveDocument.sk_star.addConstraint(Sketcher.Constraint('Parallel',1,11)) 
App.ActiveDocument.sk_star.addConstraint(Sketcher.Constraint('Parallel',2,7)) 
App.ActiveDocument.sk_star.addConstraint(Sketcher.Constraint('Parallel',5,10)) 
App.ActiveDocument.sk_star.addConstraint(Sketcher.Constraint('Parallel',8,13)) 
#
App.ActiveDocument.sk_star.addConstraint(Sketcher.Constraint('PointOnObject',2,2,0)) 
App.ActiveDocument.sk_star.addConstraint(Sketcher.Constraint('PointOnObject',5,2,2)) 
App.ActiveDocument.sk_star.addConstraint(Sketcher.Constraint('PointOnObject',8,2,5)) 
App.ActiveDocument.sk_star.addConstraint(Sketcher.Constraint('PointOnObject',11,2,1)) 
# inner star parallel constraints
App.ActiveDocument.sk_star.addConstraint(Sketcher.Constraint('Parallel',6,2)) 
App.ActiveDocument.sk_star.addConstraint(Sketcher.Constraint('Parallel',3,4)) 
App.ActiveDocument.sk_star.addConstraint(Sketcher.Constraint('Parallel',14,1)) 
App.ActiveDocument.sk_star.addConstraint(Sketcher.Constraint('Parallel',12,13)) 
App.ActiveDocument.sk_star.addConstraint(Sketcher.Constraint('Parallel',9,10)) 
# outer star parallel constraints (parallelograms)
App.ActiveDocument.sk_star.addConstraint(Sketcher.Constraint('Equal',3,14)) 
App.ActiveDocument.sk_star.addConstraint(Sketcher.Constraint('Equal',3,6)) 
App.ActiveDocument.sk_star.addConstraint(Sketcher.Constraint('Equal',6,9)) 
App.ActiveDocument.sk_star.addConstraint(Sketcher.Constraint('Equal',9,12)) 
# inner star equal forward leg length
App.ActiveDocument.sk_star.addConstraint(Sketcher.Constraint('Equal',0,2)) 
App.ActiveDocument.sk_star.addConstraint(Sketcher.Constraint('Equal',2,5)) 
App.ActiveDocument.sk_star.addConstraint(Sketcher.Constraint('Equal',5,8)) 
#App.ActiveDocument.sk_star.addConstraint(Sketcher.Constraint('Equal',8,11)) 
# tie shield and star together
App.ActiveDocument.sk_star.addConstraint(Sketcher.Constraint('PointOnObject',1,1,3)) 
App.ActiveDocument.sk_star.addConstraint(Sketcher.Constraint('PointOnObject',4,1,6)) 
App.ActiveDocument.sk_star.addConstraint(Sketcher.Constraint('PointOnObject',7,1,9)) 
App.ActiveDocument.sk_star.addConstraint(Sketcher.Constraint('PointOnObject',10,1,12)) 
App.ActiveDocument.sk_star.addConstraint(Sketcher.Constraint('PointOnObject',0,1,14)) 
#
App.ActiveDocument.sk_star.addConstraint(Sketcher.Constraint('DistanceY',6,2,-1,1,31.396127)) 
App.ActiveDocument.sk_star.addConstraint(Sketcher.Constraint('DistanceY',-1,1,0,1,25.400165)) 

# Macro End: /home/amcintosh/Documents/FreeCAD/tests/Macro/star.FCMacro +++++++++++++++++++++++++++++++++++++++++++++++++

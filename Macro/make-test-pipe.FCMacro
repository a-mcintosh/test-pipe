# -*- coding: utf-8 -*-

# Macro Begin: /home/amcintosh/Documents/FreeCAD/tests/Macro/make-test-drawing.FCMacro +++++++++++++++++++++++++++++++++++++++++++++++++
import FreeCAD
import PartDesign
import PartDesignGui
import Sketcher
import Part
import math

App.newDocument("test-pipe")
App.ActiveDocument.addObject('PartDesign::Body','Body')
App.ActiveDocument.addObject('PartDesign::AdditiveBox','Box')
App.ActiveDocument.Body.addObject(App.ActiveDocument.Box)
App.ActiveDocument.Box.Length=304.800
App.ActiveDocument.Box.Width=304.800
App.ActiveDocument.Box.Height=304.800

# -------------------------------------
Gui.getDocument("test_pipe").getObject("Box").Visibility=True
Gui.activeView().setActiveObject('pdbody',App.ActiveDocument.findObjects('PartDesign::Body')[0])
App.ActiveDocument.Body.newObject('PartDesign::Plane','dp_diagonal')
FreeCAD.Console.PrintMessage("line 22\n")
#  --  if the following recompute is removed, then inexplicable trouble.
App.ActiveDocument.recompute()
App.ActiveDocument.dp_diagonal.Support = [(App.ActiveDocument.Box,'Vertex5'),(App.ActiveDocument.Box,'Vertex4'),(App.ActiveDocument.Box,'Vertex6')]
FreeCAD.Console.PrintMessage("line 23\n")
App.activeDocument().dp_diagonal.MapMode = 'ThreePointsPlane'
App.ActiveDocument.dp_diagonal.MapReversed = False
FreeCAD.Console.PrintMessage("line 26\n")
# -------------------------------------
App.ActiveDocument.Body.newObject('Sketcher::SketchObject','sk_diagonal')
App.ActiveDocument.sk_diagonal.Support = (App.ActiveDocument.dp_diagonal, [''])
App.ActiveDocument.sk_diagonal.MapMode = 'FlatFace'
App.ActiveDocument.sk_diagonal.addGeometry(Part.Point(App.Vector(143.511322,203.200000,0)))
App.ActiveDocument.recompute()
App.ActiveDocument.sk_diagonal.addGeometry(Part.Point(App.Vector(-287.379808,-101.600000,0)))
App.ActiveDocument.recompute()
App.ActiveDocument.sk_diagonal.addGeometry(Part.LineSegment(App.Vector(143.514826,203.200000,0),App.Vector(-287.376382,-101.600000,0)),False)
App.ActiveDocument.sk_diagonal.addConstraint(Sketcher.Constraint('Coincident',2,1,0,1)) 
App.ActiveDocument.sk_diagonal.addConstraint(Sketcher.Constraint('Coincident',2,2,1,1)) 
App.ActiveDocument.recompute()
#Gui.activeDocument().activeView().viewIsometric()
App.ActiveDocument.recompute()

App.ActiveDocument.Body.newObject('PartDesign::Plane','dp_starSupport')
App.ActiveDocument.dp_starSupport.AttachmentOffset.Base.z=-25.4*12*1.732
App.ActiveDocument.dp_starSupport.Support = [(App.ActiveDocument.sk_diagonal,'Edge1')]
App.ActiveDocument.dp_starSupport.MapMode = 'NormalToEdge'
# -------------------------------------------1
this_sketch = App.ActiveDocument.Body.newObject('Sketcher::SketchObject','sk_star')
App.ActiveDocument.sk_star.Support = (App.ActiveDocument.dp_starSupport, '')
App.ActiveDocument.sk_star.MapMode = 'FlatFace'

rot = App.Rotation(App.Vector(0, 0, 1),360/5)
ratio_inside = math.cos(2*math.pi/5)/math.cos(2*math.pi/10)
ratio_outside = math.cos(2*math.pi/10)
scale_factor = 1.0/(ratio_outside*ratio_inside)
scale_grand = 5

FreeCAD.Console.PrintMessage("ratio inside " + str(ratio_inside) + "\n")
FreeCAD.Console.PrintMessage("ratio outside " + str(ratio_outside) + "\n")
FreeCAD.Console.PrintMessage("Scale factor " + str(scale_factor) + "\n")
vec = App.Vector(0, 25.4, 0)
vec.Length *= scale_grand

vec2 = App.Vector(0, -1, 0)
vec2.Length = ratio_inside * vec.Length

vec2 = rot.multVec(vec2)
vec2 = rot.multVec(vec2)
vec2 = rot.multVec(vec2)
vec1 = vec2

this_sketch.addGeometry(Part.LineSegment(vec,vec2),False)

vec = rot.multVec(vec)
this_sketch.addGeometry(Part.LineSegment(vec,vec2),False)
vec2 = rot.multVec(vec2)
this_sketch.addGeometry(Part.LineSegment(vec,vec2),False)
this_sketch.addGeometry(Part.LineSegment(scale_factor*vec1,scale_factor*vec2),True)
vec1 = vec2

vec = rot.multVec(vec)
this_sketch.addGeometry(Part.LineSegment(vec,vec2),False)
vec2 = rot.multVec(vec2)
this_sketch.addGeometry(Part.LineSegment(vec,vec2),False)
this_sketch.addGeometry(Part.LineSegment(scale_factor*vec1,scale_factor*vec2),True)
vec1 = vec2

vec = rot.multVec(vec)
this_sketch.addGeometry(Part.LineSegment(vec,vec2),False)
vec2 = rot.multVec(vec2)
this_sketch.addGeometry(Part.LineSegment(vec,vec2),False)
this_sketch.addGeometry(Part.LineSegment(scale_factor*vec1,scale_factor*vec2),True)
vec1 = vec2

vec = rot.multVec(vec)
this_sketch.addGeometry(Part.LineSegment(vec,vec2),False)
vec2 = rot.multVec(vec2)
this_sketch.addGeometry(Part.LineSegment(vec,vec2),False)
this_sketch.addGeometry(Part.LineSegment(scale_factor*vec1,scale_factor*vec2),True)
vec1 = vec2

vec = rot.multVec(vec)
this_sketch.addGeometry(Part.LineSegment(vec,vec2),False)
vec2 = rot.multVec(vec2)
this_sketch.addGeometry(Part.LineSegment(scale_factor*vec1,scale_factor*vec2),True)

#outer star
this_sketch.addConstraint(Sketcher.Constraint('Coincident',2,1,1,1)) 
this_sketch.addConstraint(Sketcher.Constraint('Coincident',0,2,1,2)) 
this_sketch.addConstraint(Sketcher.Constraint('Coincident',5,1,4,1)) 
this_sketch.addConstraint(Sketcher.Constraint('Coincident',8,1,7,1)) 
this_sketch.addConstraint(Sketcher.Constraint('Coincident',11,1,10,1)) 
this_sketch.addConstraint(Sketcher.Constraint('Coincident',13,1,0,1)) 
#inner star
this_sketch.addConstraint(Sketcher.Constraint('Coincident',4,2,2,2)) 
this_sketch.addConstraint(Sketcher.Constraint('Coincident',7,2,5,2)) 
this_sketch.addConstraint(Sketcher.Constraint('Coincident',10,2,8,2)) 
this_sketch.addConstraint(Sketcher.Constraint('Coincident',13,2,11,2))
# inner pentangle
this_sketch.addConstraint(Sketcher.Constraint('Coincident',3,2,6,1)) 
this_sketch.addConstraint(Sketcher.Constraint('Coincident',6,2,9,1)) 
this_sketch.addConstraint(Sketcher.Constraint('Coincident',9,2,12,1)) 
this_sketch.addConstraint(Sketcher.Constraint('Coincident',12,2,14,1)) 
this_sketch.addConstraint(Sketcher.Constraint('Coincident',14,2,3,1)) 
#make arms have parallel segments
this_sketch.addConstraint(Sketcher.Constraint('Parallel',0,4)) 
this_sketch.addConstraint(Sketcher.Constraint('Parallel',1,11)) 
this_sketch.addConstraint(Sketcher.Constraint('Parallel',2,7)) 
this_sketch.addConstraint(Sketcher.Constraint('Parallel',5,10)) 
this_sketch.addConstraint(Sketcher.Constraint('Parallel',8,13)) 
#
this_sketch.addConstraint(Sketcher.Constraint('PointOnObject',2,2,0)) 
this_sketch.addConstraint(Sketcher.Constraint('PointOnObject',5,2,2)) 
this_sketch.addConstraint(Sketcher.Constraint('PointOnObject',8,2,5)) 
this_sketch.addConstraint(Sketcher.Constraint('PointOnObject',11,2,1)) 
# inner star parallel constraints
this_sketch.addConstraint(Sketcher.Constraint('Parallel',6,2)) 
this_sketch.addConstraint(Sketcher.Constraint('Parallel',3,4)) 
this_sketch.addConstraint(Sketcher.Constraint('Parallel',14,1)) 
this_sketch.addConstraint(Sketcher.Constraint('Parallel',12,13)) 
this_sketch.addConstraint(Sketcher.Constraint('Parallel',9,10)) 
# outer star parallel constraints (parallelograms)
this_sketch.addConstraint(Sketcher.Constraint('Equal',3,14)) 
this_sketch.addConstraint(Sketcher.Constraint('Equal',3,6)) 
this_sketch.addConstraint(Sketcher.Constraint('Equal',6,9)) 
this_sketch.addConstraint(Sketcher.Constraint('Equal',9,12)) 
# inner star equal forward leg length
this_sketch.addConstraint(Sketcher.Constraint('Equal',0,2)) 
this_sketch.addConstraint(Sketcher.Constraint('Equal',2,5)) 
this_sketch.addConstraint(Sketcher.Constraint('Equal',5,8)) 
#this_sketch.addConstraint(Sketcher.Constraint('Equal',8,11)) 
# tie shield and star together
this_sketch.addConstraint(Sketcher.Constraint('PointOnObject',1,1,3)) 
this_sketch.addConstraint(Sketcher.Constraint('PointOnObject',4,1,6)) 
this_sketch.addConstraint(Sketcher.Constraint('PointOnObject',7,1,9)) 
this_sketch.addConstraint(Sketcher.Constraint('PointOnObject',10,1,12)) 
this_sketch.addConstraint(Sketcher.Constraint('PointOnObject',0,1,14)) 
#
this_sketch.addConstraint(Sketcher.Constraint('DistanceY',6,2,-1,1,scale_grand*31.396127)) 
this_sketch.addConstraint(Sketcher.Constraint('DistanceY',-1,1,0,1,scale_grand*25.400165)) 
# -------------------------------------------

this_pipe = App.ActiveDocument.Body.newObject("PartDesign::SubtractivePipe","SubtractivePipe")
App.ActiveDocument.SubtractivePipe.Profile = App.ActiveDocument.sk_star
App.ActiveDocument.SubtractivePipe.Spine = App.ActiveDocument.sk_diagonal
Gui.activeDocument().hide(App.ActiveDocument.Box.Name)
App.ActiveDocument.recompute()
FreeCAD.Console.PrintMessage("line 172\n")
Gui.ActiveDocument.SubtractivePipe.ShapeColor=(0.545098066329956, 0.7372549176216125, 0.4470588266849518, 0.0)
Gui.ActiveDocument.getObject(this_pipe.Name).Transparency = 50
Gui.activeDocument().activeView().setCameraOrientation(App.Rotation(0.3421, 0.385, 0.34, 0.758))
Gui.SendMsgToActiveView("ViewFit")
# Macro End: /home/amcintosh/Documents/FreeCAD/tests/Macro/make-test-pipe.FCMacro +++++++++++++++++++++++++++++++++++++++++++++++++

# -*- coding: utf-8 -*-

# Macro Begin: /home/amcintosh/Documents/FreeCAD/tests/Macro/test-pipe-3.FCMacro +++++++++++++++++++++++++++++++++++++++++++++++++
import FreeCAD
import PartDesign
import PartDesignGui
import Sketcher

this_document = App.newDocument("test-pipe-star")
App.setActiveDocument(this_document.Name)
App.activeDocument().addObject('PartDesign::Body','Body')
App.ActiveDocument.addObject('PartDesign::AdditiveBox','Box')
App.ActiveDocument.Body.addObject(App.activeDocument().Box)
App.ActiveDocument.Box.Length=152.400
App.ActiveDocument.Box.Width=152.400
App.ActiveDocument.Box.Height=152.400
#
App.activeDocument().Body.newObject('PartDesign::Plane','DatumPlane001')
App.activeDocument().DatumPlane001.Support = \
  [(this_document.Box,'Vertex4'),(this_document.Box,'Vertex5'),(this_document.Box,'Vertex1')]
App.activeDocument().DatumPlane001.MapMode = 'ThreePointsPlane'
#
App.ActiveDocument.Body.newObject('Sketcher::SketchObject','boreLine')
this_document.boreLine.MapMode = "FlatFace"
this_document.boreLine.Support = [(this_document.DatumPlane001,'')]
this_document.boreLine.addGeometry(Part.LineSegment(App.Vector(-101.600000,-143.876782,0),App.Vector(69.850000,98.425000,0)),False)

# Macro End: /home/amcintosh/Documents/FreeCAD/tests/Macro/test-pipe-3.FCMacro +++++++++++++++++++++++++++++++++++++++++++++++++

# -*- coding: utf-8 -*-

# Macro Begin: /home/amcintosh/Documents/FreeCAD/test-pipe/Macro/repeat-test-box.FCMacro +++++++++++++++++++++++++++++++++++++++++++++++++
import FreeCAD
import PartDesign
import PartDesignGui
import Sketcher

App.activeDocument().addObject('PartDesign::Body','Body')
#Gui.activateView('Gui::View3DInventor', True)
#Gui.activeView().setActiveObject('pdbody', App.activeDocument().Body)
App.ActiveDocument.addObject('PartDesign::AdditiveBox','Box')
App.ActiveDocument.Body.addObject(App.activeDocument().Box)
App.ActiveDocument.recompute()
#Gui.ActiveDocument.Box.ShapeColor=Gui.ActiveDocument.Body.ShapeColor
#Gui.ActiveDocument.Box.LineColor=Gui.ActiveDocument.Body.LineColor
#Gui.ActiveDocument.Box.PointColor=Gui.ActiveDocument.Body.PointColor
#Gui.ActiveDocument.Box.Transparency=Gui.ActiveDocument.Body.Transparency
#Gui.ActiveDocument.Box.DisplayMode=Gui.ActiveDocument.Body.DisplayMode
#Gui.activeDocument().setEdit('Box')
App.ActiveDocument.Box.Length=76.200
App.ActiveDocument.Box.Width=76.200
App.ActiveDocument.Box.Height=76.200

App.ActiveDocument.recompute()
App.ActiveDocument.recompute()
#Gui.activeDocument().resetEdit()
#Gui.activeDocument().activeView().viewIsometric()
#Gui.SendMsgToActiveView("ViewFit")
App.activeDocument().Body.newObject('PartDesign::Plane','DatumPlane')
App.activeDocument().DatumPlane.Support = [(App.getDocument('Unnamed').Box,'Vertex4'),(App.getDocument('Unnamed').Box,'Vertex5'),(App.getDocument('Unnamed').Box,'Vertex6')]
App.activeDocument().DatumPlane.MapMode = 'ThreePointsPlane'
App.activeDocument().recompute()
#Gui.activeDocument().setEdit('DatumPlane')
#Gui.activateWorkbench("SketcherWorkbench")
App.ActiveDocument.DatumPlane.MapReversed = False
App.ActiveDocument.DatumPlane.Support = [(App.getDocument('Unnamed').Box,'Vertex4'),(App.getDocument('Unnamed').Box,'Vertex5'),(App.getDocument('Unnamed').Box,'Vertex6')]
App.ActiveDocument.DatumPlane.MapMode = 'ThreePointsPlane'
App.ActiveDocument.recompute()
#Gui.ActiveDocument.resetEdit()
#Gui.activateWorkbench('PartDesignWorkbench')
App.activeDocument().Body.newObject('Sketcher::SketchObject','Sketch')
App.activeDocument().Sketch.Support = (App.activeDocument().DatumPlane, [''])
App.activeDocument().Sketch.MapMode = 'FlatFace'
App.ActiveDocument.recompute()
#Gui.activeDocument().setEdit('Sketch')
#Gui.activateWorkbench('SketcherWorkbench')
#ActiveSketch = App.ActiveDocument.getObject('Sketch')
#tv = Show.TempoVis(App.ActiveDocument)
#if ActiveSketch.ViewObject.HideDependent:
#  objs = tv.get_all_dependent(ActiveSketch)
#  objs = filter(lambda x: not x.TypeId.startswith("TechDraw::"), objs)
#  objs = filter(lambda x: not x.TypeId.startswith("Drawing::"), objs)
#  tv.hide(objs)
#if ActiveSketch.ViewObject.ShowSupport:
#  tv.show([ref[0] for ref in ActiveSketch.Support if not ref[0].isDerivedFrom("PartDesign::Plane")])
#if ActiveSketch.ViewObject.ShowLinks:
#  tv.show([ref[0] for ref in ActiveSketch.ExternalGeometry])
#tv.hide(ActiveSketch)
#ActiveSketch.ViewObject.TempoVis = tv
#del(tv)
#
#ActiveSketch = App.ActiveDocument.getObject('Sketch')
#if ActiveSketch.ViewObject.RestoreCamera:
#  ActiveSketch.ViewObject.TempoVis.saveCamera()
#
#Gui.activeDocument().activeView().viewIsometric()
App.ActiveDocument.Sketch.addGeometry(Part.LineSegment(App.Vector(-35.675506,50.616702,0),App.Vector(71.752285,-25.454839,0)),False)
App.ActiveDocument.recompute()
#Gui.getDocument('Unnamed').resetEdit()
#ActiveSketch = App.ActiveDocument.getObject('Sketch')
#tv = ActiveSketch.ViewObject.TempoVis
#if tv:
#  tv.restore()
#ActiveSketch.ViewObject.TempoVis = None
#del(tv)
#
#Gui.activateWorkbench('PartDesignWorkbench')
App.getDocument('Unnamed').recompute()
App.activeDocument().Body.newObject('PartDesign::Plane','DatumPlane001')
App.activeDocument().DatumPlane001.Support = [(App.getDocument('Unnamed').Sketch,'Edge1')]
App.activeDocument().DatumPlane001.MapMode = 'NormalToEdge'
App.activeDocument().recompute()
#Gui.activeDocument().setEdit('DatumPlane001')
App.ActiveDocument.DatumPlane001.MapReversed = False
App.ActiveDocument.DatumPlane001.Support = [(App.getDocument('Unnamed').Sketch,'Edge1')]
App.ActiveDocument.DatumPlane001.MapMode = 'NormalToEdge'
App.ActiveDocument.recompute()
#Gui.ActiveDocument.resetEdit()
App.activeDocument().Body.newObject('Sketcher::SketchObject','Sketch001')
App.activeDocument().Sketch001.Support = (App.activeDocument().DatumPlane001, '')
App.activeDocument().Sketch001.MapMode = 'FlatFace'
App.ActiveDocument.recompute()
#Gui.activeDocument().setEdit('Sketch001')
#Gui.activateWorkbench('SketcherWorkbench')
#ActiveSketch = App.ActiveDocument.getObject('Sketch001')
#tv = Show.TempoVis(App.ActiveDocument)
#if ActiveSketch.ViewObject.HideDependent:
#  objs = tv.get_all_dependent(ActiveSketch)
#  objs = filter(lambda x: not x.TypeId.startswith("TechDraw::"), objs)
#  objs = filter(lambda x: not x.TypeId.startswith("Drawing::"), objs)
#  tv.hide(objs)
#if ActiveSketch.ViewObject.ShowSupport:
#  tv.show([ref[0] for ref in ActiveSketch.Support if not ref[0].isDerivedFrom("PartDesign::Plane")])
#if ActiveSketch.ViewObject.ShowLinks:
#  tv.show([ref[0] for ref in ActiveSketch.ExternalGeometry])
#tv.hide(ActiveSketch)
#ActiveSketch.ViewObject.TempoVis = tv
#del(tv)
#
#ActiveSketch = App.ActiveDocument.getObject('Sketch001')
#if ActiveSketch.ViewObject.RestoreCamera:
#  ActiveSketch.ViewObject.TempoVis.saveCamera()
#
App.ActiveDocument.Sketch001.addGeometry(Part.LineSegment(App.Vector(11.554865,-18.174125,0),App.Vector(12.700000,17.003364,0)),False)
App.ActiveDocument.Sketch001.addConstraint(Sketcher.Constraint('Vertical',0)) 
App.ActiveDocument.recompute()
App.ActiveDocument.Sketch001.addGeometry(Part.LineSegment(App.Vector(11.554863,17.003365,0),App.Vector(-19.050000,15.875000,0)),False)
App.ActiveDocument.Sketch001.addConstraint(Sketcher.Constraint('Coincident',1,1,0,2)) 
App.ActiveDocument.recompute()
App.ActiveDocument.Sketch001.addGeometry(Part.LineSegment(App.Vector(-19.050000,15.875000,0),App.Vector(11.554865,-18.174125,0)),False)
App.ActiveDocument.Sketch001.addConstraint(Sketcher.Constraint('Coincident',2,1,1,2)) 
App.ActiveDocument.Sketch001.addConstraint(Sketcher.Constraint('Coincident',2,2,0,1)) 
App.ActiveDocument.recompute()
#Gui.activeDocument().activeView().viewIsometric()
#Gui.activeDocument().activeView().viewFront()
#Gui.activeDocument().activeView().viewTop()
#Gui.getDocument('Unnamed').resetEdit()
#ActiveSketch = App.ActiveDocument.getObject('Sketch001')
#tv = ActiveSketch.ViewObject.TempoVis
#if tv:
#  tv.restore()
#ActiveSketch.ViewObject.TempoVis = None
#del(tv)
#
#Gui.activateWorkbench('PartDesignWorkbench')
this_pipe = App.ActiveDocument.Body.newObject("PartDesign::SubtractivePipe","SubtractivePipe")
App.ActiveDocument.SubtractivePipe.Profile = App.ActiveDocument.Sketch001
App.ActiveDocument.SubtractivePipe.Spine = App.ActiveDocument.Sketch
Gui.activeDocument().hide(App.ActiveDocument.Box.Name)
App.getDocument('Unnamed').recompute()
App.ActiveDocument.recompute()
#Gui.activeDocument().resetEdit()
#Gui.SendMsgToActiveView("ViewFit")
#Gui.getDocument("Unnamed").getObject("SubtractivePipe").Visibility=False
#Gui.getDocument("Unnamed").getObject("SubtractivePipe").Visibility=True
#Gui.getDocument("Unnamed").getObject("DatumPlane001").Visibility=False
#Gui.getDocument("Unnamed").getObject("DatumPlane001").Visibility=True
#Gui.getDocument("Unnamed").getObject("DatumPlane").Visibility=False
#Gui.getDocument("Unnamed").getObject("DatumPlane").Visibility=True
#Gui.getDocument("Unnamed").getObject("Box").Visibility=True
#Gui.getDocument("Unnamed").getObject("Box").Visibility=False
#Gui.getDocument("Unnamed").getObject("DatumPlane").Visibility=False
#Gui.getDocument("Unnamed").getObject("DatumPlane").Visibility=True
#Gui.getDocument("Unnamed").getObject("DatumPlane001").Visibility=False
#Gui.getDocument("Unnamed").getObject("DatumPlane001").Visibility=True
#Gui.getDocument("Unnamed").getObject("Sketch001").Visibility=False
#Gui.getDocument("Unnamed").getObject("Sketch001").Visibility=True
#Gui.getDocument("Unnamed").getObject("Sketch").Visibility=False
#Gui.getDocument("Unnamed").getObject("Sketch").Visibility=True
# Macro End: /home/amcintosh/Documents/FreeCAD/test-pipe/Macro/repeat-test-box.FCMacro +++++++++++++++++++++++++++++++++++++++++++++++++
